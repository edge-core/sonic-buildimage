module sonic-dscp-fc-map {

    yang-version 1.1;

    namespace "http://github.com/Azure/sonic-dscp-fc-map";

    prefix dtm;

    organization
        "SONiC";

    contact
        "SONiC";

    description
        "DSCP_TO_FC_MAP yang Module for SONiC OS";

    revision 2021-10-29 {
        description
            "Initial revision.";
    }

    container sonic-dscp-fc-map {

        container DSCP_TO_FC_MAP {

            description "DSCP_TO_FC_MAP part of config_db.json";

            list DSCP_TO_FC_MAP_LIST {

                key "name";

                leaf name {
                    type string {
                        pattern '[a-zA-Z0-9]{1}([-a-zA-Z0-9_]{0,31})';
                        length 1..32 {
                            error-message "Invalid length for map name.";
                            error-app-tag map-name-invalid-length;
                        }
                    }
                }

                list DSCP_TO_FC_MAP { //this is list inside list for storing mapping between two fields

                    key "dscp";

                    leaf dscp {
                        type string {
                            pattern "6[0-3]|[1-5][0-9]?|[0-9]?" {
                                error-message "Invalid DSCP";
                                error-app-tag dscp-invalid;
                            }
                        }
                    }

                    leaf fc {
                        type string {
                            pattern "[0-7]?" {
                                error-message "Invalid Forwarding Class";
                                error-app-tag fc-invalid;
                            }
                        }
                    }
                }
            }
        }
    }
}
