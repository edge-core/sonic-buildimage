module sonic-events-host {
    namespace "http://github.com/sonic-net/sonic-events-host";
    yang-version 1.1;
    prefix events-host;

    import sonic-events-common {
        prefix evtcmn;
        revision-date 2022-12-01;
    }

    import sonic-types {
        prefix stypes;
    }

    organization
        "SONiC";

    contact
        "SONiC";

    description
        "YANG schema defined for host events";

    revision 2022-12-01 {
        description "BGP alert events.";
    }

    container sonic-events-host {
        container disk-usage {
            evtcmn:ALARM_SEVERITY_MINOR;

            description "
                Declares an event for disk usage crossing set limit
                The parameters describe the usage & limit set.";
            
            leaf fs {
                type string;
                description "Name of the file system";
            }

            uses evtcmn:sonic-events-usage;

            uses evtcmn:sonic-events-cmn;
        }

        container memory-usage {
            evtcmn:ALARM_SEVERITY_MINOR;

            description "
                Declares an event for memory usage crossing set limit
                The parameters describe the usage & limit set.";
            
            uses evtcmn:sonic-events-usage;

            uses evtcmn:sonic-events-cmn;
        }

        container cpu-usage {
            evtcmn:ALARM_SEVERITY_MINOR;
            description "
                Declares an event for cpu usage crossing set limit
                The parameters describe the usage & limit set.";
            
            uses evtcmn:sonic-events-usage;

            uses evtcmn:sonic-events-cmn;
        }

        container event-sshd {
            evtcmn:ALARM_SEVERITY_MINOR;

            description "
                Declares and event reported by sshd.
                This implies an internal system state blocks sshd from
                creating the new user.";

            leaf username {
                type string;
                description "Name of the new user";
            }

            uses evtcmn:sonic-events-cmn;
        }

        container event-disk {
            evtcmn:ALARM_SEVERITY_MINOR;

            description "
                Declares an event reported by disk check.
                The fail type declares the type of failure.
                read-only - denotes that disk is in RO state.";

            leaf fail_type {
                type enumeration {
                    enum "read_only";
                }
                description "Type of failure";
            }

            uses evtcmn:sonic-events-cmn;
        }

        container event-kernel {
            evtcmn:ALARM_SEVERITY_MINOR;

            description "
                Declares an event reported by kernel.
                The fail type declares the type of failure.";

            leaf fail_type {
                type enumeration {
                    enum "write_failed";
                    enum "write_protected";
                    enum "remount_read_only";
                    enum "zlib_decompress";
                }
                description "Type of failure";
            }

            uses evtcmn:sonic-events-cmn;
        }

        container event-down-ctr {
            evtcmn:EVENT_SEVERITY_2;

            description "
                Declares an container that is expected to be up is down.
                Reported by monit periodically.";
               
            leaf ctr_name {
                type string;
                description "Name of the container not running";
            }

            uses evtcmn:sonic-events-cmn;
        }

        container event-stopped-ctr {
            evtcmn:EVENT_SEVERITY_2;

            description "
                Declare an event at the time point of container stopping.
                event-down-ctr fires periodically until it starts up.";
               
            leaf ctr_name {
                type string;
                description "Name of the container";
            }

            uses evtcmn:sonic-events-cmn;
        }

        container watchdog-timeout {
            evtcmn:EVENT_SEVERITY_2;

            description "
                Declares an event for watchdog timeout failure.
                Params:
                    limit provides max timeout limit";

            leaf limit {
                type uint8;
                description "Timeout limit";
            }

            uses evtcmn:sonic-events-cmn;
        }

        container event-seu {
            evtcmn:EVENT_SEVERITY_2;

            description "
                Declares an event for SEU error.";

            uses evtcmn:sonic-events-cmn;
        }

        container invalid-freelist {
            evtcmn:EVENT_SEVERITY_2;

            description "
                Declares an event for invalid freelist failure.";

            uses evtcmn:sonic-events-cmn;
        }

        container mem-threshold-exceeded {
            evtcmn:EVENT_SEVERITY_2;

            description "
                Declares an event for memory exceeding threshold failure.";

            leaf ctr_name {
                type stypes:ctr_name;
                description "Container name of mem-threshold-exceeded event";
            }

            leaf mem_usage {
                type uint64;
                description "Memory usage of process";
            }

            leaf threshold {
                type uint64;
                description "Threshold value of process";
            }

            uses evtcmn:sonic-events-cmn;
        }

        container process-exited-unexpectedly {
            evtcmn:EVENT_SEVERITY_2;

            description "
                Declares an event in which a critical process exits unexpectedly.";

            leaf process_name {
                type stypes:process_name;
                description "Name of process that is exiting unexpectedly";
            }

            leaf ctr_name {
                type stypes:ctr_name;
                description "Container name of process that is exiting unexpectedly";
            }

            uses evtcmn:sonic-events-cmn;
        }

        container process-not-running {
            evtcmn:EVENT_SEVERITY_2;

            description "
                Declares an event in which a critical process exits unexpectedly.";

            leaf process_name {
                type stypes:process_name; 
                description "Name of process that is not running";
            }

            leaf ctr_name {
                type stypes:ctr_name;
                description "Container name";
            }

            uses evtcmn:sonic-events-cmn;
        }
    }
}
