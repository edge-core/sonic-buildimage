module sonic-bgp-device-global {
    namespace "http://github.com/sonic-net/sonic-bgp-device-global";
    prefix bgp_device_global;
    yang-version 1.1;

    organization
        "SONiC";

    contact
        "SONiC";

    description
        "SONIC Device-specific BGP global data";

    revision 2022-06-26 {
        description
            "Initial revision";
    }

    container sonic-bgp-device-global {
        container BGP_DEVICE_GLOBAL {
            container STATE {
                description "BGP device-specific global data";
                leaf tsa_enabled {
                    type boolean;
                    default "false";
                    description
                    "When set to true, Traffic is shifted away (TSA), i.e, BGP routes are not advertised to neighboring routers";
                }
            } /* end of STATE container */
        } /* end of BGP_DEVICE_GLOBAL container */

    } /* end of top level container */

} /* end of module sonic-bgp-device-global */
