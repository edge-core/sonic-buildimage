module sonic-events-common {
    namespace "http://github.com/sonic-net/sonic-events-common";
    prefix evtcmn;
    yang-version 1.1;

    import ietf-yang-types {
        prefix yang;
    }

    organization
        "SONiC";

    contact
        "SONiC";

    description
        "SONIC Events common definition";

    revision 2022-12-01 {
        description
            "Common reusable definitions";
    } 

    grouping sonic-events-cmn {
        leaf timestamp {
            type yang:date-and-time;
            description "time of the event";
        }
    }

    grouping sonic-events-usage {
        leaf usage {
            type decimal64 {
                fraction-digits 1;
            }
            description "Percentage in use";
        }
        
        leaf limit {
            type decimal64 {
                fraction-digits 1;
            }
            description "Percentage limit set";
        }
    }

    extension EVENT_SEVERITY_2 {
        description
            "Indicates that the severity level of this type of event is 2";
    }

     extension EVENT_SEVERITY_3 {
        description
            "Indicates that the severity level of this type of event is 3";
    }

     extension EVENT_SEVERITY_4 {
        description
            "Indicates that the severity level of this type of event is 4";
    }

    extension ALARM_SEVERITY_MINOR {
        description
            "Indicates the existence of a non-service affecting fault condition 
             and that corrective action should be taken in order to prevent a more serious
             (for example, service affecting) fault. Such a severity can be reported, 
             for example, when the detected alarm condition is not currently degrading the capacity of the resource";
    }

    extension ALARM_SEVERITY_MAJOR {
        description
            "Indicates that a service affecting condition has developed and an urgent corrective 
             action is required. Such a severity can be reported, for example, when there is a severe 
             degradation in the capability of the resource and its full capability must be restored.";
    }
}
