module sonic-extension {

    yang-version 1.1;

    namespace "http://github.com/Azure/sonic-extension";
    prefix sonic-extension;

    description "Extension yang Module for SONiC OS";

    revision 2019-07-01 {
        description "First Revision";
    }
}
