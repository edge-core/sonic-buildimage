module sonic-stp {
    namespace "http://github.com/Azure/sonic-stp";
    prefix sstp;
    yang-version 1.1;

    import sonic-port {
        prefix prt;
    }

    import sonic-portchannel {
        prefix spc;
    }

    import sonic-vlan {
        prefix svlan;
    }

    organization
        "SONiC";

    contact
        "SONiC";

    description
        "SONIC STP";

    revision 2024-08-28 {
        description
            "Initial revision.";
    }

    container sonic-stp {

        container STP {

            list STP_LIST {
                key "name";
                unique "name";
                leaf name {
                    type string {
                        pattern "GLOBAL";
                    }
                }

                leaf mode {
                    type enumeration {
                        enum mstp;
                        enum rstp;
                        enum stp;
                        enum pvst;
                        enum rpvst;
                    }
                }

                leaf rootguard_timeout {
                     type uint16 {
                        range "5..600" {
                            error-message "Global root guard timeout out of range";
                            error-app-tag rootguard-timeout-invalid;
                        }
                    }
                }

                leaf forward_delay {
                     type uint8 {
                        range "4..30" {
                            error-message "Global forward delay out of range";
                            error-app-tag forward-delay-invalid;
                        }
                    }
                }

                leaf hello_time {
                     type uint8 {
                        range "1..10" {
                            error-message "Global hello interval out of range";
                            error-app-tag hello-time-invalid;
                        }
                    }
                }

                leaf max_age {
                     type uint8 {
                        range "6..40" {
                            error-message "Global max age time out of range";
                            error-app-tag max-age-invalid;
                        }
                    }
                }

                leaf priority {
                     type uint16 {
                        range "0..61440" {
                            error-message "Global bridge priority out of range";
                            error-app-tag priority-invalid;
                        }
                    }
                }
            }
        }

        container STP_VLAN {

            list STP_VLAN_LIST {
                key "if_name";

                leaf if_name {
                    type leafref {
                        path "/svlan:sonic-vlan/svlan:VLAN/svlan:VLAN_LIST/svlan:name";
                    }
                }

                leaf forward_delay {
                     type uint8 {
                        range "4..30" {
                            error-message "Vlan forward delay out of range";
                            error-app-tag forward-delay-invalid;
                        }
                    }
                }

                leaf hello_time {
                     type uint8 {
                        range "1..10" {
                            error-message "Vlan hello interval out of range";
                            error-app-tag hello-time-invalid;
                        }
                    }
                }

                leaf max_age {
                     type uint8 {
                        range "6..40" {
                            error-message "Vlan max age time out of range";
                            error-app-tag max-age-invalid;
                        }
                    }
                }

                leaf priority {
                     type uint16 {
                        range "0..61440" {
                            error-message "Vlan bridge priority out of range";
                            error-app-tag priority-invalid;
                        }
                    }
                }

                leaf enabled {
                    type boolean;
                }
            }
        }

        container STP_VLAN_PORT {

            list STP_VLAN_PORT_LIST {
                key "name ifname";

                leaf name {
                    type leafref {
                        path "/svlan:sonic-vlan/svlan:VLAN/svlan:VLAN_LIST/svlan:name";
                    }
                }

                leaf ifname {
                    type union {
                        type leafref {
                            path "/prt:sonic-port/prt:PORT/prt:PORT_LIST/prt:name";
                        }
                        type leafref {
                            path "/spc:sonic-portchannel/spc:PORTCHANNEL/spc:PORTCHANNEL_LIST/spc:name";
                        }
                    }
                }

                leaf path_cost {
                     type uint32 {
                        range "1..200000000" {
                            error-message "Per vlan port path cost out of range";
                            error-app-tag path-cost-invalid;
                        }
                    }
                }

                leaf priority {
                     type uint8 {
                        range "0..240" {
                            error-message "Per vlan port priority out of range";
                            error-app-tag priority-invalid;
                        }
                    }
                }
            }
        }

        container STP_PORT {

            list STP_PORT_LIST {
                key "ifname";

                leaf ifname {
                    type union {
                        type leafref {
                            path "/prt:sonic-port/prt:PORT/prt:PORT_LIST/prt:name";
                        }
                        type leafref {
                            path "/spc:sonic-portchannel/spc:PORTCHANNEL/spc:PORTCHANNEL_LIST/spc:name";
                        }
                    }
                }

                leaf enabled {
                    type boolean;
                }

                leaf root_guard {
                    type boolean;
                }

                leaf bpdu_guard {
                    type boolean;
                }

                leaf bpdu_guard_do_disable {
                    type boolean;
                }

                leaf path_cost {
                     type uint32 {
                        range "1..200000000" {
                            error-message "Port path cost out of range";
                            error-app-tag path-cost-invalid;
                        }
                    }
                }

                leaf priority {
                     type uint8 {
                        range "0..240" {
                            error-message "Port priority out of range";
                            error-app-tag priority-invalid;
                        }
                    }
                }

                leaf portfast {
                    type boolean;
                }

                leaf uplink_fast {
                    type boolean;
                }
            }
        }
    }
}
