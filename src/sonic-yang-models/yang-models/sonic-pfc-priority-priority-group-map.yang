module sonic-pfc-priority-priority-group-map {

    yang-version 1.1;

    namespace "http://github.com/sonic-net/sonic-pfc-priority-priority-group-map";

    prefix pppgm;

    organization
        "SONiC";

    contact
        "SONiC";

    description
        "PFC_PRIORITY_TO_PRIORITY_GROUP_MAP yang Module for SONiC OS";

    revision 2021-04-15 {
        description
            "Initial revision.";
    }

    container sonic-pfc-priority-priority-group-map {    

        container PFC_PRIORITY_TO_PRIORITY_GROUP_MAP {

            description "PFC_PRIORITY_TO_PRIORITY_GROUP_MAP part of config_db.json";

            list PFC_PRIORITY_TO_PRIORITY_GROUP_MAP_LIST {

                key "name";

                leaf name {
                    type string {
                        pattern '[a-zA-Z0-9]{1}([-a-zA-Z0-9_]{0,31})';
                        length 1..32 {
                            error-message "Invalid length for map name.";
                            error-app-tag map-name-invalid-length;
                        }
                    }
                }

                list PFC_PRIORITY_TO_PRIORITY_GROUP_MAP { //this is list inside list for storing mapping between two fields

                    key "pfc_priority";

                    leaf pfc_priority {
                        type string {
                            pattern "[0-7]?" {
                               error-message "Invalid pfc priority";
                               error-app-tag pfc-priority-invalid;
                            }
                        }
                    }

                    leaf pg {
                        type string {
                            pattern "[0-7]?" {
                                error-message "Invalid Priority Group";
                                error-app-tag pg-invalid;
                            }
                        }
                    }
                }
            }
        }
    }
}
